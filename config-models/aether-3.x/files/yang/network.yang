module network {
  namespace "http://opennetworking.org/aether/network";
  prefix net;

  import aether-types{ prefix at; }
  import enterprise{ prefix ent; }
  import ietf-yang-types{ prefix yg; }

  organization "Open Networking Foundation.";
  contact "Scott Baker";
  description 
    "An Aether Network is a cellular network, defined by its
     MCC and MNC.";

  revision "2021-06-02" {
    description "An Aether Network";
    reference "RFC 6087";
  }

  typedef network-id {
        type yg:yang-identifier {
            length 1..32;
        }
  }

  container network {
    description "The top level container";

    list network {
      key "id";
      description
        "List of networks";

      leaf id {
        type network-id;
        description "ID for this network.";
      }

      leaf display-name {
        type string {
            length 1..80;
        }
        description "display name to use in GUI or CLI";
      }

      leaf mcc {
        type at:mcc;
        mandatory true;
        description "mobile country code";
      }

      leaf mnc {
        type at:mnc;
        mandatory true;
        description "mobile network code";
      }   

      leaf description {
        type string {
          length 1..100;
        }
        description "description of this network";
      }

      // Network may be owned by an Enterprise, or it may be a shared network provided by Aether.
      leaf enterprise {
        type leafref {
          path "/ent:enterprise/ent:enterprise/ent:id";
        }
        mandatory true;
        description
          "Link to enterprise that owns this Network. If this is set to None, then the Network is globally provided by Aether.";
      }      
    }
  } 
}
