module upf-list {
  namespace "http://opennetworking.org/aether/upf-list";
  prefix upf;

  import ietf-inet-types { prefix inet; }  

  organization "Open Networking Foundation.";
  contact "Scott Baker";
  description "A Aether UPF List is a named list of User Plane Functions.";

  revision "2021-06-02" {
    description "An Aether User Plane Function";
    reference "RFC 6087";
  }

  typedef upf-list-id {
        type string {
            length 1..32;
        }
  }

  container upf-list {
    description "The top level container";

    list upf-list {
      key "id";
      description
        "A list of named upf-lists.";

      leaf id {
        type upf-list-id;
        description "ID for this upf.";
      }

      list addresses {
        key "address";
        leaf address {
          type inet:host;
          description
            "Address of UPF";
        }
        leaf allow {
          type boolean;
          default true;
          description
            "Allow or deny this UPF";
        }
        description
          "List of UPF addresses";
      }       

      leaf display-name {
        type string {
            length 1..80;
        }
        description "display name to use in GUI or CLI";
      }

      leaf description {
        type string {
          length 1..100;
        }
        description "description of this UPF";
      }
    }
  } 
}
